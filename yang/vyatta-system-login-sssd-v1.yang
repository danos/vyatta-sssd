module vyatta-system-login-sssd-v1 {
	namespace "urn:vyatta.com:mgmt:vyatta-system-login-sssd:1";
	prefix vyatta-system-login-sssd-v1;

	import vyatta-system-v1 {
		prefix system;
	}
	import vyatta-system-login-v1 {
		prefix system-login;
	}
	import configd-v1 {
		prefix configd;
	}

	organization "AT&T Inc.";
	contact
		"AT&T
		 Postal: 208 S. Akard Street
		         Dallas, TX 75202
		 Web: www.att.com";

	description
		"Copyright (c) 2018, AT&T Intellectual Property.
		 All rights reserved.

		 Copyright (c) 2014-2017 by Brocade Communications Systems, Inc.
		 All rights reserved.

         Redistribution and use in source and binary forms, with or without
         modification, are permitted provided that the following conditions
         are met:

         1. Redistributions of source code must retain the above copyright
            notice, this list of conditions and the following disclaimer.
         2. Redistributions in binary form must reproduce the above
            copyright notice, this list of conditions and the following
            disclaimer in the documentation and/or other materials provided
            with the distribution.
         3. Neither the name of the copyright holder nor the names of its
            contributors may be used to endorse or promote products derived
            from this software without specific prior written permission.

         THIS SOFTWARE IS PROVIDED BY THE COPYRIGHT HOLDERS AND CONTRIBUTORS
         'AS IS' AND ANY EXPRESS OR IMPLIED WARRANTIES, INCLUDING, BUT NOT
         LIMITED TO, THE IMPLIED WARRANTIES OF MERCHANTABILITY AND FITNESS
         FOR A PARTICULAR PURPOSE ARE DISCLAIMED. IN NO EVENT SHALL THE
         COPYRIGHT HOLDER OR CONTRIBUTORS BE LIABLE FOR ANY DIRECT, INDIRECT,
         INCIDENTAL, SPECIAL, EXEMPLARY, OR CONSEQUENTIAL DAMAGES (INCLUDING,
         BUT NOT LIMITED TO, PROCUREMENT OF SUBSTITUTE GOODS OR SERVICES;
         LOSS OF USE, DATA, OR PROFITS; OR BUSINESS INTERRUPTION) HOWEVER
         CAUSED AND ON ANY THEORY OF LIABILITY, WHETHER IN CONTRACT, STRICT
         LIABILITY, OR TORT (INCLUDING NEGLIGENCE OR OTHERWISE) ARISING IN
         ANY WAY OUT OF THE USE OF THIS SOFTWARE, EVEN IF ADVISED OF THE
         POSSIBILITY OF SUCH DAMAGE.

         SPDX-License-Identifier: BSD-3-Clause

		 The YANG module for vyatta-system-login-sssd-v1";

	revision 2018-07-19 {
		description "Adds missing ordered-by node for auth-chain method.
		Auth-chain method is dependent of what order the method is listed
		in.";
	}
	revision 2015-08-14 {
		description "Initial revision of version 1.";
	}

	augment /system:system/system-login:login {
		container auth-chain {
			configd:help "Authentication chain";
			leaf-list method {
				configd:help "Authentication method";
				ordered-by "user";
				type enumeration {
					enum "tacplus" {
						configd:help "TACACS+ authentication";
					}
					enum "local" {
						configd:help "Local authentication";
					}
				}
			}
		}
	}
}
